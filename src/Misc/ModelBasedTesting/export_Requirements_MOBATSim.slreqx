# export_Requirements_MOBATSim

## #1: scenario_VSA_01_destinationReached (Functional)
| Test Description | Specified Status | Expected Result |
| --- | --- | --- |
| The vehicle has reached its destination | destinationReached = 1 StatusEmergencyCase = 0 FrontSensorData = 1000 | emergencyCase = -1 leaderDistance = -1 |

## #2: scenario_VSA_02_CollisionEvent (Functional)
| Test Description | Specified Status | Expected Result |
| --- | --- | --- |
| The vehicle has not reached its destination and collided with other vehicles | destinationReached = 0 StatusEmergencyCase = 3 FrontSensorData = 1000 | emergencyCase = 3 leaderDistance = FrontSensorData |

## #3: scenario_VSA_03_NoVehicleAhead (Functional)
| Test Description | Specified Status | Expected Result |
| --- | --- | --- |
| The vehicle has not reached its destination, there is no other vehicle in front of the ego vehicle | destinationReached = 0 StatusEmergencyCase = 0 FrontSensorData = 200 | emergencyCase = 0 leaderDistance = FrontSensorData |

## #4: scenario_VSA_04_VehicleAhead-FarAway (Functional)
| Test Description | Specified Status | Expected Result |
| --- | --- | --- |
| The vehicle has not reached its destination, the vehicle ahead is far away from the ego vehicle | destinationReached = 0 StatusEmergencyCase = 1 FrontSensorData = 80 | emergencyCase = 1 leaderDistance = FrontSensorData |

## #5: scenario_VSA_05_VehicleAhead-VeryClose (Functional)
| Test Description | Specified Status | Expected Result |
| --- | --- | --- |
| The vehicle has not reached its destination, the vehicle in front is very close to the ego vehicle | destinationReached = 0 StatusEmergencyCase = 2 FrontSensorData = 15 | emergencyCase = 2 leaderDistance = FrontSensorData |

## #6: scenario_VSA_06_BugSituation (Functional)
| Test Description | Specified Status | Expected Result |
| --- | --- | --- |
| The vehicle has not reached its destination, the described scenario is a bug | destinationReached = 0 StatusEmergencyCase = 2 FrontSensorData = -50 | emergencyCase = 2 leaderDistance = FrontSensorData |

## #7: scenario_BP_01_destinationReached (Functional)
| Test Description | Specified Status | Expected Result |
| --- | --- | --- |
| -The vehicle has reached its destination | destinationReached = 1 | SpeedReference =0 DistanceReference = -1 LeadSpeed = -1 DrivingMode = 1 Dist2Stop = -1 |

## #8: scenario_BP_02_NoVehicleAhead-CruiseControl (Functional)
| Test Description | Specified Status | Expected Result |
| --- | --- | --- |
| -The vehicle has not reached its destination -There is no vehicle ahead | destinationReached = 0 stopAt = 0 emergencyCase = 0 CurrentSpeed= 20 LeaderDistance = 1000 LeaderSpeed = 0 | LeadSpeed = LeaderSpeed SpeedReference = maxSpeed DistanceReference= LeaderDistance DrivingMode = 1 Dist2Stop = 0 |

## #9: scenario_BP_03_VehicleAhead-Far-PlatoonControl (Functional)
| Test Description | Specified Status | Expected Result |
| --- | --- | --- |
| -The vehicle has not reached its destination -The vehicle has to follow a preceding vehicle, the distance between vehicles is greater than the safe distance | destinationReached = 0 stopAt = 0 emergencyCase = 1 CurrentSpeed = 20 LeaderDistance = 60 LeaderSpeed = 15 | LeadSpeed = LeaderSpeed SpeedReference = maxSpeed DistanceReference = LeaderDistance DrivingMode = 2 Dist2Stop = 0 |

## #10: scenario_BP_04_VehicleAhead-Near-PlatoonControl (Functional)
| Test Description | Specified Status | Expected Result |
| --- | --- | --- |
| -The vehicle has not reached its destination -The vehicle has to follow a preceding vehicle, the distance between vehicles is less than the safe distance, but the speed of ego vehicle is less than the speed of the preceding vehicle | destinationReached = 0 stopAt = 0 emergencyCase = 2 CurrentSpeed = 12 LeaderDistance = 15 LeaderSpeed = 20 | LeadSpeed = LeaderSpeed SpeedReference = maxSpeed DistanceReference = LeaderDistance DrivingMode = 2 Dist2Stop = 0 |

## #11: scenario_BP_05_VehicleAhead-Near-EmergencyBrakeControl (Functional)
| Test Description | Specified Status | Expected Result |
| --- | --- | --- |
| -The vehicle has not reached its destination -The vehicle has to follow a preceding vehicle, the distance between vehicles is less than the safe distance, and the speed of ego vehicle is greater than the speed of the preceding vehicle | destinationReached = 0 stopAt = 0 emergencyCase = 2 CurrentSpeed = 20 LeaderDistance = 15 LeaderSpeed = 10 | LeadSpeed = LeaderSpeed SpeedReference = maxSpeed DistanceReference = LeaderDistance DrivingMode = 3 Dist2Stop = 0 |

## #12: scenario_BP_06_CollisionEvent (Functional)
| Test Description | Specified Status | Expected Result |
| --- | --- | --- |
| -The vehicle has not reached its destination -The vehicle has collided with other vehicles | destinationReached = 0 stopAt = 0 emergencyCase = 3 CurrentSpeed = 0 LeaderDistance = 40 LeaderSpeed = 15 | LeadSpeed = LeaderSpeed SpeedReference = maxSpeed DistanceReference = LeaderDistance DrivingMode = 1 Dist2Stop = 0 |

## #13: scenario_BP_07_NoVehicleAhead-SafeStopControl (Functional)
| Test Description | Specified Status | Expected Result |
| --- | --- | --- |
| -The vehicle has not reached its destination -The vehicle at waypoint 36 receives a safe stop command, should stop at the waypoint 12 -There is no vehicle ahead | destinationReached = 0 stopAt = 12 emergencyCase = 0 CurrentSpeed= 20 LeaderDistance = 1000 LeaderSpeed = 0 VehiclePosition= coordinates of waypoint 36 (20,0,140) StopPosition= coordinates of waypoint 12 (-110,0,250) | LeadSpeed = LeaderSpeed SpeedReference = maxSpeed DistanceReference= LeaderDistance DrivingMode = 4 Dist2Stop = norm(VehiclePosition -StopPosition) |

## #14: scenario_BP_08_VehicleAhead-Near(dominated)&SafeStop (Functional)
| Test Description | Specified Status | Expected Result |
| --- | --- | --- |
| -The vehicle has not reached its destination -The vehicle at waypoint 36 receives a safe stop command,should stop at the waypoint 12 -The vehicle has to follow a preceding vehicle, the distance between vehicles is less than the safe distance, and the speed of ego vehicle is greater than the speed of the preceding vehicle | destinationReached = 0 stopAt = 12 emergencyCase = 2 CurrentSpeed = 15 LeaderDistance = 15 LeaderSpeed = 10 VehiclePosition = coordinates of waypoint 36 (20,0,140) StopPosition = coordinates of waypoint 12 (-110,0,250) | LeadSpeed = LeaderSpeed SpeedReference = maxSpeed DistanceReference = LeaderDistance DrivingMode = 3 Dist2Stop = norm(VehiclePosition - StopPosition) |

## #15: scenario_BP_09_VehicleAhead-Far&SafeStop(dominated) (Functional)
| Test Description | Specified Status | Expected Result |
| --- | --- | --- |
| -The vehicle has not reached its destination -The vehicle at waypoint 7 receives a safe stop command,should stop at the waypoint 27 -The vehicle has to follow a preceding vehicle, the distance between vehicles is greater than the safe distance | destinationReached = 0 stopAt = 27 emergencyCase = 1 CurrentSpeed = 15 LeaderDistance = 80 LeaderSpeed = 20 VehiclePosition = coordinates of waypoint 7 (-220,0,90) StopPosition = coordinates of waypoint 27 (170,0,90) | LeadSpeed = LeaderSpeed SpeedReference = maxSpeed DistanceReference = LeaderDistance DrivingMode = 4 Dist2Stop = norm(VehiclePosition - StopPosition) |

## #16: scenario_BP_10_VehicleAhead-Near&SafeStop(dominated) (Functional)
| Test Description | Specified Status | Expected Result |
| --- | --- | --- |
| -The vehicle has not reached its destination -The vehicle at waypoint 21 receives a safe stop command,should stop at the waypoint 15 -The vehicle has to follow a preceding vehicle, the distance between vehicles is less than the safe distance, but the speed of ego vehicle is less than the speed of the preceding vehicle | destinationReached = 0 stopAt = 15 emergencyCase = 2 CurrentSpeed= 10 LeaderDistance = 15 LeaderSpeed = 20 VehiclePosition= coordinates of waypoint 36 (190,0,310) StopPosition= coordinates of waypoint 12 (-190,0,480) | LeadSpeed = LeaderSpeed SpeedReference = maxSpeed DistanceReference= LeaderDistance DrivingMode = 4 Dist2Stop = norm(VehiclePosition -StopPosition) |

## #18: scenario_LSC_01_NoVehicleAhead-DrivingMode1 (Functional)
| Test Description | Specified Status | Expected Result |
| --- | --- | --- |
| -The vehicle is running -No safe stop command -There is no vehicle ahead | SpeedReference = 20 InterVehicularDistance = 1000 LeadSpeed = 0 DrivingMode = 1 Dist2Stop = 0 | ActualSpeed<=SpeedReference MeasuredSpeed = ActualSpeed |

## #19: scenario_LSC_02_VehicleAhead-Far-DrivingMode2(egoVehicleSlower) (Functional)
| Test Description | Specified Status | Expected Result |
| --- | --- | --- |
| -The vehicle is running -No safe stopcommand -There is a vehicle in front of ego vehicle, the distance between vehicles is greater than the safe distance, and ego vehicle is slower than the preceding vehicle | SpeedReference = 20 InterVehicularDistance = 1000(0~10s) -> 80~40(10~20s) LeadSpeed = 0(0~10s) -> 30(10~20s) DrivingMode = 1(0~10s) -> 2(10~20s) Dist2Stop = 0 | When DrivingMode=1: ActualSpeed<=Speed Reference MeasuredSpeed = ActualSpeed When DrivingMode=2 and ego vehicle is slower than the preceding vehicle, ego vehicle can maintain its own speed: ActualSpeed = SpeedReference MeasuredSpeed = ActualSpeed |

## #20: scenario_LSC_03_VehicleAhead-Far-DrivingMode2(egoVehicleFaster) (Functional)
| Test Description | Specified Status | Expected Result |
| --- | --- | --- |
| -The vehicle is running -No safe stopcommand -There is a vehicle in front of ego vehicle, the distance between vehicles is greater than the safe distance, but ego vehicle is faster than the preceding vehicle | SpeedReference = 20 InterVehicularDistance = 1000(0~10s) -> 80~40(10~20s) LeadSpeed = 0(0~10s) -> 10(10~20s) DrivingMode = 1(0~10s) -> 2(10~20s) Dist2Stop = 0 | When DrivingMode=1: ActualSpeed<=Speed Reference MeasuredSpeed = ActualSpeed When DrivingMode=2 and ego vehicle is faster than the preceding vehicle, it is necessary to detect that ego vehicle has decelerated at least once: ActualSpeed<=LeadSpeed MeasuredSpeed = ActualSpeed |

## #21: scenario_LSC_04_VehicleAhead-Near-DrivingMode2(egoVehicleSlower) (Functional)
| Test Description | Specified Status | Expected Result |
| --- | --- | --- |
| -The vehicle is running -No safe stopcommand -There is a vehicle in front of ego vehicle, the distance between vehicles is less than the safe distance, and ego vehicle is slower than the preceding vehicle | SpeedReference = 20 InterVehicularDistance = 1000(0~10s) -> 20~5(10~20s) LeadSpeed = 0(0~10s) -> 30(10~20s) Driving Mode = 1(0~10s) -> 2(10~20s) Dist2Stop = 0 | When DrivingMode=1: ActualSpeed<=SpeedReference MeasuredSpeed = ActualSpeed When DrivingMode=2 and ego vehicle is slower than the preceding vehicle, ego vehicle can maintain its own speed: ActualSpeed = SpeedReference MeasuredSpeed = ActualSpeed |

## #22: scenario_LSC_05_VehicleAhead-Near-DrivingMode3(egoVehicleFaster) (Functional)
| Test Description | Specified Status | Expected Result |
| --- | --- | --- |
| -The vehicle is running -No safe stopcommand -There is a vehicle in front of ego vehicle, the distance between vehicles is less than the safe distance, but ego vehicle is faster than the preceding vehicle | SpeedReference = 20 InterVehicularDistance = 1000(0~10s) -> 10~5(10~20s) LeadSpeed = 0(0~10s) -> 5(10~20s) Driving Mode = 1(0~10s) -> 3(10~20s) Dist2Stop = 0 | When DrivingMode=1: ActualSpeed <= SpeedReference MeasuredSpeed = ActualSpeed When DrivingMode=3, it is necessary to detect that the vehicle has made an emergency braking: (duration(DrivingMode==3) >1) ActualSpeed = 0 MeasuredSpeed = ActualSpeed |

## #23: scenario_LSC_06_NoVehicleAhead-DrivingMode4 (Functional)
| Test Description | Specified Status | Expected Result |
| --- | --- | --- |
| -The vehicle is running -receives a safe stop command -There is no vehicle ahead | Speed Reference = 20 InterVehicularDistance = 1000 Lead Speed = 0 Driving Mode = 1(0~10s) -> 4(10~20s) Dist2Stop = 0(0~10s) -> 100~0(10~20s) -> 0(20~30s) | When DrivingMode=1: ActualSpeed <= SpeedReference MeasuredSpeed = ActualSpeed When DrivingMode=4 and no vehicle ahead: When the distance between the vehicle and thestopping place is 0, the speed of the vehicle should be 0: (duration(Dist2Stop == 0) > 2) ActualSpeed = 0 MeasuredSpeed = 0 |

## #24: scenario_LSC_07_VehicleAhead-Far-DrivingMode4(egoVehicleSlower) (Functional)
| Test Description | Specified Status | Expected Result |
| --- | --- | --- |
| -The vehicle is running -receives a safe stop command -There is a vehicle in front of ego vehicle, the distance between vehicles is greater than the safe distance, and ego vehicle is slower than the preceding vehicle | SpeedReference = 20 InterVehicularDistance = 1000(0~10s) -> 80~40(10~30s) LeadSpeed = 0(0~10s) -> 30(10~30s) DrivingMode = 1(0~10s) -> 4(10~30s) Dist2Stop = 0(0~10s) -> 100~0(10~20s) -> 0(20~30s) | When DrivingMode=1: ActualSpeed <= SpeedReference MeasuredSpeed = ActualSpeed When DrivingMode=4 and no vehicle ahead: When the distance between the vehicle and thestopping place is 0, the speed of the vehicle should be 0: (duration(Dist2Stop == 0) > 2) ActualSpeed = 0 MeasuredSpeed = 0 |

## #33: scenario_LSC_08_VehicleAhead-Far-DrivingMode4(egoVehicleFaster) (Functional)
| Test Description | Specified Status | Expected Result |
| --- | --- | --- |
| -The vehicle is running -receives a safe stop command -There is a vehicle in front of ego vehicle, the distance between vehicles is greater than the safe distance, but ego vehicle is faster than the preceding vehicle | SpeedReference = 20 InterVehicularDistance = 1000(0~10s) -> 80~40(10~30s) LeadSpeed = 0(0~10s) -> 10(10~30s) DrivingMode = 1(0~10s) -> 4(10~30s) Dist2Stop = 0(0~10s) -> 100~0(10~20s) -> 0(20~30s) | When DrivingMode=1: ActualSpeed<=SpeedReference MeasuredSpeed = ActualSpeed When DrivingMode=4 and no vehicle ahead: When the distance between the vehicle and thestopping place is 0, the speed of the vehicle should be 0: (duration(Dist2Stop == 0) > 2) ActualSpeed = 0 MeasuredSpeed = 0 |

## #34: scenario_LSC_09_VehicleAhead-Near-DrivingMode4(egoVehicleSlower) (Functional)
| Test Description | Specified Status | Expected Result |
| --- | --- | --- |
| -The vehicle is running -receives a safe stop command -There is a vehicle in front of ego vehicle, the distance between vehicles is less than the safe distance, and ego vehicle is slower than the preceding vehicle | SpeedReference = 20 InterVehicularDistance = 1000(0~10s) -> 15~10(10~30s) LeadSpeed = 0(0~10s) -> 10(10~30s) DrivingMode = 1(0~10s) -> 4(10~30s) Dist2Stop = 0(0~10s) -> 100~0(10~20s) -> 0(20~30s) | When DrivingMode=1: ActualSpeed<=SpeedReference MeasuredSpeed = ActualSpeed When DrivingMode=4 and no vehicle ahead: When the distance between the vehicle and thestopping place is 0, the speed of the vehicle should be 0: (duration(Dist2Stop == 0) > 2) ActualSpeed = 0 MeasuredSpeed = 0 |

## #35: scenario_LSCPC_01_VehicleAhead-Far(egoVehicleSlower) (Functional)
| Test Description | Specified Status | Expected Result |
| --- | --- | --- |
| -The vehicle is running -There is a vehicle in front of ego vehicle, the distance between vehicles is greater than the safe distance, and ego vehicle is slower than the preceding vehicle | Inter Vehicular Distance = 50->80 Lead Speed = 30 Vehicle Speed = 20 | ref speed = Lead Speed |

## #36: scenario_LSCPC_02_VehicleAhead-Far(egoVehicleFaster) (Functional)
| Test Description | Specified Status | Expected Result |
| --- | --- | --- |
| -The vehicle is running -There is a vehicle in front of ego vehicle, the distance between vehicles is greater than the safe distance, and ego vehicle is faster than the preceding vehicle | Inter Vehicular Distance = 70->40 Lead Speed = 10 Vehicle Speed = 20 | ref speed < Vehicle Speed |

## #37: scenario_LSCPC_03_VehicleAhead-Near(egoVehicleSlower) (Functional)
| Test Description | Specified Status | Expected Result |
| --- | --- | --- |
| -The vehicle is running -There is a vehicle in front of ego vehicle, the distance between vehicles is less than the safe distance, and ego vehicle is slower than the preceding vehicle | Inter Vehicular Distance = 10->22 Lead Speed = 16 Vehicle Speed = 12 | ref speed = Lead Speed |

## #38: scenario_LSCSC_01_PlatoonControlDominated (Functional)
| Test Description | Specified Status | Expected Result |
| --- | --- | --- |
| Speed​​Ref from Platoon <= 0.02*DistanceToStop, PlatoonControl is dominated | Speed Ref from Platoon = -5~1.5 Distance to Stop = 100 | refSpeed = Speed Ref from Platoon |

## #39: scenario_LSCSC_02_StopControlDominated (Functional)
| Test Description | Specified Status | Expected Result |
| --- | --- | --- |
| Speed​​Ref from Platoon > 0.02*Distance to Stop, SafeStopControl is dominated | Speed Ref from Platoon = 5~1 Distance to Stop = 40 | refSpeed = 0.02*Distance to Stop |

## #47: scenario_LSCAC_01_CruiseControl (Functional)
| Test Description | Specified Status | Expected Result |
| --- | --- | --- |
| DrivingMode = 1, the vehicle will select CruiseControl | Driving Mode = 1 Speed Error = 20~5~20 Actual Speed = 0~15~0 | Acceleration Command > = -40&&Acceleration Command <= 6 If 0< Actual speed <3 and Speed Error >6, then Acceleration Command == 6; If 3< Actual speed <6 and Speed Error >5, then Acceleration Command == 5; If 6< Actual speed <9 and Speed Error >3.8, then Acceleration Command == 3.8; If 9< Actual speed <12 and Speed Error >3, then Acceleration Command == 3; If 12< Actual speed <14 and Speed Error >2.2, then Acceleration Command == 2.2; If Actual speed >14 and Speed Error >1.4, then Acceleration Command == 1.4; |

## #48: scenario_LSCAC_02_PlatoonControl (Functional)
| Test Description | Specified Status | Expected Result |
| --- | --- | --- |
| DrivingMode = 2, the vehicle will select PlatoonControl | Driving Mode = 2 Speed Error = -50~20 Actual Speed = 20~0 | Acceleration Command > = -40 && Acceleration Command <= 6 If 0< Actual speed <3 and Speed Error >6, then Acceleration Command == 6; If 3< Actual speed <6 and Speed Error >5, then Acceleration Command == 5; If 6< Actual speed <9 and Speed Error >3.8, then Acceleration Command == 3.8; If 9< Actual speed <12 and Speed Error >3, then Acceleration Command == 3; If 12< Actual speed <14 and Speed Error >2.2, then Acceleration Command == 2.2; If Actual speed >14 and Speed Error >1.4, then Acceleration Command == 1.4; |

## #49: scenario_LSCAC_03_EmergencyBrakeControl (Functional)
| Test Description | Specified Status | Expected Result |
| --- | --- | --- |
| DrivingMode = 3, the vehicle will select EmergencyBrakeControl | Driving Mode = 3 Speed Error = -50~20 Actual Speed = 20~0 | Acceleration Command > = -40 && Acceleration Command <= 6 If 0< Actual speed <3 and Speed Error >6, then Acceleration Command == 6; If 3< Actual speed <6 and Speed Error >5, then Acceleration Command == 5; If 6< Actual speed <9 and Speed Error >3.8, then Acceleration Command == 3.8; If 9< Actual speed <12 and Speed Error >3, then Acceleration Command == 3; If 12< Actual speed <14 and Speed Error >2.2, then Acceleration Command == 2.2; If Actual speed >14 and Speed Error >1.4, then Acceleration Command == 1.4; |

## #50: scenario_LSCAC_04_SafeStopControl (Functional)
| Test Description | Specified Status | Expected Result |
| --- | --- | --- |
| DrivingMode = 4, the vehicle will select SafeStopControl | Driving Mode = 4 Speed Error = -50~20 Actual Speed = 20~0 | Acceleration Command > = -40 && Acceleration Command <= 6 If 0< Actual speed <3 and Speed Error >6, then Acceleration Command == 6; If 3< Actual speed <6 and Speed Error >5, then Acceleration Command == 5; If 6< Actual speed <9 and Speed Error >3.8, then Acceleration Command == 3.8; If 9< Actual speed <12 and Speed Error >3, then Acceleration Command == 3; If 12< Actual speed <14 and Speed Error >2.2, then Acceleration Command == 2.2; If Actual speed >14 and Speed Error >1.4, then Acceleration Command == 1.4; |

## #37: scenario_LSC_10_VehicleAhead-Near-DrivingMode2(egoVehicleFaster) (Functional)
| Test Description | Specified Status | Expected Result |
| --- | --- | --- |
| -The vehicle is running -No safe stopcommand -There is a vehicle in front of ego vehicle, the distance between vehicles is less than the safe distance, but ego vehicle is faster than the preceding vehicle | SpeedReference = 20 InterVehicularDistance = 1000(0~10s) -> 10~5(10~20s) LeadSpeed = 0(0~10s) ->5(10~20s) Driving Mode = 1(0~10s) ->2(10~20s) Dist2Stop = 0 | When DrivingMode=1: ActualSpeed <= SpeedReference MeasuredSpeed = ActualSpeed When DrivingMode=2 and ego vehicle is faster than the preceding vehicle, the distance between vehicles is also less than the safe distance - it is necessary to detect that the vehicle has made a deceleration: ActualSpeed <= LeadSpeed MeasuredSpeed = ActualSpeed |
