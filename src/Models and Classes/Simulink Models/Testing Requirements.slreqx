# Testing Requirements
Requirements for automated Testing of Scenarios 1-11.

S1: Urban City Traffic
S2: Curved Road Overtaking
S3: Road Merge Collision
S4: Platoon Control
S5: High Speed Collision
S6: Road Merge Collision V3,V4
S7: Complex Crossroad
S8: Extra Complex Crossroad
S9: Counterexample Crossroad Safety
S10: Carmageddon
S11: Convoy Platoons

## #3: Scenario 1 - Urban City Traffic (Functional)
Urban City Traffic
- Vehicle 2 makes lane change on straight road
- Vehicle 5 change planned path
startingPoints = [46 47 84 3 54 64 58 57 4 63];
destinationPoints = [54 51 82 26 3 42 27 25 26 47];
maxSpeeds = [3 18 3 7 14 10 0.1 4 10 10];

### #1: Scenario 1 - Urban City Traffic - Vehicle 5 (Functional)
Vehicle 5 change planned path
- Keywords: Scenario 1, Urbann City Traffic

### #2: Scenario 1 - Urban City Traffic - Vehicle 2 (Functional)
Vehicle 2 makes lane change on straight road

## #5: Scenario 2 - Curved Road Overtaking (Functional)
Curved Road Overtaking
- Vehicle 2 makes lane change on curved road
- Vehicle 5 change planned Path
startingPoints = [46 29 84 3 54 64 58 57 4 63];
destinationPoints = [54 24 82 26 3 42 27 25 26 47];
maxSpeeds = [3 18 3 7 14 10 0.1 4 10 10];

### #7: Scenario 2 - Curved Road Overtaking - Vehicle 5 (Functional)
Vehicle 5 change planned path

### #19: Scenario 2 - Curved Road Overtaking - Vehicle 2 (Functional)
Vehicle 2 makes lane change on curved road

## #8: Scenario 3 - Road Merge Collision (Functional)
Road Merge Collision
- Road merging Vehicle Convoy Scenario
- V5 stops and blocks the road merge causing a collision
startingPoints = [50 46 15 3 54 52 6 7 47 30];
destinationPoints = [13 17 20 11 25 41 18 31 15 39];
maxSpeeds = [13 12.9 12 9.2 13 13 12.8 13.8 6 13];

## #11: Scenario 4 - Platoon Control (Functional)
Platoon Control
- Platoon control test for vehicle convoy
startingPoints = [51 47 48 3 55 53 6 7 22 45];
destinationPoints = [13 15 18 27 26 40 27 32 16 10];
maxSpeeds = [13 13 11 9 13 15 12 14 4 13];

## #12: Scenario 5 - High Speed Collision (Functional)
High Speed Collision
- V3 hits V4 with high speed - front collision
startingPoints = [46 47 7 27 85 52 64 57 15 63];
destinationPoints = [54 51 26 26 23 27 42 25 59 47];
maxSpeeds = [3 15 35 1 6 10 10 12 10 10];

## #13: Scenario 7 - Complex Crossroad (Functional)
Complex Crossroad
- Complex crossroad scenario + V8 collides with V1
startingPoints = [8 46 29 18 41 52 64 6 15 63];
destinationPoints = [26 47 51 1 3 27 42 25 7 46];
maxSpeeds = [20 15 10 10 14 20 10 12 10 10];

## #14: Scenario 6 - Road Merge Collision V3, V4 (Functional)
Road Merge Collision V3, V4
- V3 merges the road from left while V4 goes straight and collides
startingPoints = [46 47 6 7 85 52 64 57 15 63];
destinationPoints = [54 51 27 26 27 23 42 25 59 47];
maxSpeeds = [3 15 10 5.55 6 10 10 12 10 10];

## #15: Scenario 8 - Extra Complex Crossroad (Functional)
Extra Complex Crossroad
- Extra complex crossroad scenario
startingPoints = [8 46 29 18 53 52 65 6 15 64];
destinationPoints = [59 47 51 1 3 27 42 25 60 46];
maxSpeeds = [20 20 10 10 14 20 15 12 10 20];

## #16: Scenario 9 - Counterexample Crossroad Safety (Functional)
Counterexample Crossroad Safety
- Counterexample crossroad safety
startingPoints = [18 72 84 3 21 65 79 19 4 20];
destinationPoints = [17 51 82 26 17 42 60 17 26 17];
maxSpeeds = [3 8.7 3 7 14 10 0.1 4 10 10];

## #17: Scenario 10 - Mayhem (Functional)
Mayhem
startingPoints = [46 53 54 51 44 9 65 27 30 6];
destinationPoints = [25 64 24 16 10 59 42 10 11 24];
maxSpeeds = [28 25 10 25 38 25 25 30 11 15];

## #18: Scenario 11 - Convoy Platoons (Functional)
Convoy Platoons
- road merging scenario
startingPoints = [51 47 48 3 55 53 6 7 22 45];
destinationPoints = [13 15 18 11 26 40 17 32 16 10];
maxSpeeds = [13 13 11 9 13 13 8 14 4 13];
